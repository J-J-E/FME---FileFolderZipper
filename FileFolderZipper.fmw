FME workspace FileFolderZipper.fmw

Creator
    GEOMTYPE = Geometry Object
    NUM = 1
    CREATED -> FeatureReader [INITIATOR]
FeatureReader
    ATTRIBUTES = PATH,"path_unix,path_windows,path_rootname,path_filename,path_extension,path_filesize,path_ownername,path_readonly,path_modified_date,path_created_date,path_accessed_date,path_directory_unix,path_directory_windows,path_type,fme_geometry{0}"
    ATTR_ACCUM_MODE = Only Use Result
    COMBINE_GEOM = Use Result
    DATASET = C:\Users\JohnJ\Desktop\ZipTest
    FEATURETYPES = PATH
    FORMAT = PATH
    OUTPUT_FEATURES_DISPLAY = Schema and Data Features
    PATH_GLOB_PATTERN = *
    PATH_NO_EMPTY_PROPERTIES = YES
    PATH_OFFSET_DATETIME = yes
    PATH_RECURSE_DIRECTORIES = NO
    PATH_RETRIEVE_FILE_PROPERTIES = NO
    PATH_TYPE = ANY
    PATH_USE_NON_STRING_ATTR = yes
    PATH -> AttributeKeeper
AttributeKeeper
    CREATE_BULK_MODE_FEATURES = NO
    KEEP_ATTRS = path_type,path_windows
    -> FileZipper
FileZipper
    p_DeleteInput = FALSE
    p_Path = path_windows

FME custom transformer FileZipper

Parameters:
- p_DeleteInput =
- p_Path =

Input (input)
    -> AttributeCreator
AttributeCreator
    ATTR_TABLE:
      SET_TO Path = @Value($(p_Path))
      SET_TO DeleteAfterZip = $(p_DeleteInput)
    -> Zipper
Zipper: PythonCaller
    PYTHONSOURCE:
      import fme
      import fmeobjects
      import zipfile, os, shutil


      class FeatureProcessor(object):
          """Template Class Interface:
          When using this class, make sure its name is set as the value of the 'Class
          to Process Features' transformer parameter.
          """

          def __init__(self):
              """Base constructor for class members."""
              pass

          def input(self, feature):
              """This method is called for each FME Feature entering the
              PythonCaller. If knowledge of all input Features is not required for
              processing, then the processed Feature can be emitted from this method
              through self.pyoutput(). Otherwise, the input FME Feature should be
              cached to a list class member and processed in process_group() when
              'Group by' attributes(s) are specified, or the close() method.

              :param fmeobjects.FMEFeature feature: FME Feature entering the
                  transformer.
              """
              path = feature.getAttribute('Path')
              deleteAfterZip = feature.getAttribute('DeleteAfterZip')

              def zipd(path):
                  zipf = path+".zip"
                  with zipfile.ZipFile(zipf, 'w', zipfile.ZIP_DEFLATED) as ziph:
                      length = len(path)
                      for root, dirs, files in os.walk(path):
                          folder = root[length:]  # path without "parent"
                          for file in files:
                              ziph.write(os.path.join(root, file), os.path.join(folder, file))
                  return zipf

              def zipF(path):
                  ext = os.path.splitext(path)[1]
                  basename = os.path.basename(path)
                  zipf = path.replace(ext, ".zip")
                  print(basename)
                  with zipfile.ZipFile(zipf, 'w') as ziph:
                      ziph.write(path, arcname=basename)
                  return zipf

              #Check if dir:
              if os.path.isdir(path):
                  try:
                      outputPath = zipd(path)
                      feature.setAttribute("outputPath", outputPath)
                      feature.setAttribute("ZipResult", "Success")
                  except Exception as e:
                      feature.setAttribute("ZipResult", "Failure")
                      feature.setAttribute("Exception", "e")

              if os.path.isfile(path):
                  try:
                      outputPath = zipF(path)
                      feature.setAttribute("outputPath", outputPath)
                      feature.setAttribute("ZipResult", "Success")
                  except Exception as e:
                      feature.setAttribute("ZipResult", "Failure")
                      feature.setAttribute("Exception", "e")


              if deleteAfterZip == "TRUE":
                  try:
                      shutil.rmtree(path)
                  except:
                      pass

                  try:
                      os.remove(path)
                  except:
                      pass

              self.pyoutput(feature)

          def close(self):
              """This method is called once all the FME Features have been processed
              from input().
              """
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass
    PYTHONSYMBOL = FeatureProcessor
    -> AttributeExposer
AttributeExposer
    ATTR_LIST = ZipResult,outputPath,Exception
    -> TestFilter
TestFilter
    DEFAULT_VALUE = <UNFILTERED>
    TEST_LIST = "BOOL_OP,OR,COMPOSITE_TEST,""""""1"""""",TEST_CLAUSE,TEST @Value(ZipResult) = Success",Success,"BOOL_OP,OR,COMPOSITE_TEST,""""""1"""""",TEST_CLAUSE,TEST @Value(ZipResult) = Failure",Failure
    Success -> AttributeKeeper
    Failure -> AttributeKeeper_2
AttributeKeeper
    CREATE_BULK_MODE_FEATURES = NO
    KEEP_ATTRS = outputPath,ZipResult
    -> Success (output)
Success (output)
AttributeKeeper_2
    CREATE_BULK_MODE_FEATURES = NO
    KEEP_ATTRS = ZipResult,Exception
    -> Failure (output)
Failure (output)
Zipper_2: PythonCaller
    PYTHONSOURCE:
      import fme
      import fmeobjects
      import zipfile, os, shutil


      class FeatureProcessor(object):
          """Template Class Interface:
          When using this class, make sure its name is set as the value of the 'Class
          to Process Features' transformer parameter.
          """

          def __init__(self):
              """Base constructor for class members."""
              pass

          def input(self, feature):
              """This method is called for each FME Feature entering the
              PythonCaller. If knowledge of all input Features is not required for
              processing, then the processed Feature can be emitted from this method
              through self.pyoutput(). Otherwise, the input FME Feature should be
              cached to a list class member and processed in process_group() when
              'Group by' attributes(s) are specified, or the close() method.

              :param fmeobjects.FMEFeature feature: FME Feature entering the
                  transformer.
              """
              path = feature.getAttribute('Path')
              deleteAfterZip = feature.getAttribute('DeleteAfterZip')

              def zipd(path):
                  with zipfile.ZipFile(path+".zip", 'w', zipfile.ZIP_DEFLATED) as ziph:
                      length = len(path)
                      for root, dirs, files in os.walk(path):
                          folder = root[length:]  # path without "parent"
                          for file in files:
                              ziph.write(os.path.join(root, file), os.path.join(folder, file))

              def zipF(path):
                  ext = os.path.splitext(path)[1]
                  basename = os.path.basename(path)
                  zipf = path.replace(ext, ".zip")
                  print(basename)
                  with zipfile.ZipFile(zipf, 'w') as ziph:
                      ziph.write(path, arcname=basename)

              #Check if dir:
              if os.path.isdir(path):
                  zipd(path)

              if os.path.isfile(path):
                  zipF(path)


              if deleteAfterZip == "TRUE":
                  try:
                      shutil.rmtree(path)
                  except:
                      pass

                  try:
                      os.remove(path)
                  except:
                      pass

              self.pyoutput(feature)

          def close(self):
              """This method is called once all the FME Features have been processed
              from input().
              """
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass
    PYTHONSYMBOL = FeatureProcessor
